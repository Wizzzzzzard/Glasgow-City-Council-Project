FME workspace FlowDataPuller.fmw

Creator
    GEOMTYPE = Geometry Object
    NUM = 1
    CREATED -> GET_LiveTraffic
GET_LiveTraffic: HTTPCaller
    CONNECTION_TIMEOUT_LENGTH = 60
    ERROR_ATTR = _error
    FILE_PATH_ATTR = _response_file_path
    FOLLOW_REDIRECTS = FOLLOW_WITH_GET
    HTTP_METHOD = POST
    MAX_HTTP_VERSION = HTTP_2
    MAX_TRANSFERS_IN_PROGRESS = 25
    OUTPUT_FILENAME = E:\elija\OneDrive\OneDrive - University of Strathclyde\Dissertation\1. Extract Junction and Link Data\Junction Text Files\temptraffic.csv
    REDIRECT_AUTH = ORIGINAL_DOMAIN_ONLY
    SAVE_FILE = File
    SAVE_MULTI = No
    STATUS_CODE_ATTR = _http_status_code
    TARGET_URL = https://gcc-prod-traffcom.azurewebsites.net/api/TraffcomMovement?code=fgQNq/D09o30C/Qpp1LCQpwiYsWAtPEGRPd2r4HsxkBlOgvPHJIbJQ==&format=csv&size=1800
    TRANSFER_TIMEOUT_LENGTH = 90
    UPLOAD_CONTENT_TYPE = Text (text/plain)
    UPLOAD_TYPE = Specify Upload Body
    USE_COOKIES = No
    VERIFY_SSL_CERTIFICATES = Yes
Creator_2
    GEOMTYPE = Geometry Object
    NUM = 1
    CREATED -> GET_HistoricTraffic
GET_HistoricTraffic: HTTPCaller
    CONNECTION_TIMEOUT_LENGTH = 60
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 25
    OUTPUT_FILENAME = E:\elija\OneDrive\OneDrive - University of Strathclyde\Dissertation\1. Extract Junction and Link Data\Junction Text Files\histtraffic.csv
    REDIRECT_AUTH = ORIGINAL_DOMAIN_ONLY
    SAVE_FILE = File
    SAVE_MULTI = No
    STATUS_CODE_ATTR = _http_status_code
    TARGET_URL = https://gcc.azure-api.net/traffic/v1/movement/history?size=1500&format=csv&duration=7
    TRANSFER_TIMEOUT_LENGTH = 90
    USE_COOKIES = No
    VERIFY_SSL_CERTIFICATES = Yes
