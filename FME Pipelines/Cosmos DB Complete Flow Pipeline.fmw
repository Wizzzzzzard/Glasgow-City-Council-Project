FME workspace Cosmos DB Complete Flow Pipeline.fmw

Parameters:
- DestDataset_CSV2 =
- DestDataset_JSON =
- SourceDataset_DOCUMENTDB =

Readers:
- DOCUMENTDB_1: DOCUMENTDB from $(SourceDataset_DOCUMENTDB)

Writers:
- JSON_1: JSON to $(DestDataset_JSON)
- CSV2_1: CSV2 to $(DestDataset_CSV2)

metrics (reader DOCUMENTDB_1)
    attributes: period string, source string, batchId string, periodName string, sourceName string, groupKey string, partitionKey string, time string, minute int, hour int, day int, week int, month int, quarter int, year int, minEventTime string, maxEventTime string, meta object, measurements object, added string, updated string
    -> Complete Flow Data JSON (writer JSON_1)
    -> Flow Data for Past Week CSV (writer CSV2_1)
Complete Flow Data JSON (writer JSON_1)
    attributes: period string, source string, batchId string, periodName string, sourceName string, groupKey string, partitionKey string, time string, minute int, hour int, day int, week int, month int, quarter int, year int, minEventTime string, maxEventTime string, meta json, measurements json, added string, updated string
Flow Data for Past Week CSV (writer CSV2_1)
    attributes: period string, source string, batchId string, periodName string, sourceName string, groupKey string, partitionKey string, time string, minute string, hour string, day string, week string, month string, quarter string, year string, minEventTime string, maxEventTime string, meta string, measurements string, added string, updated string
