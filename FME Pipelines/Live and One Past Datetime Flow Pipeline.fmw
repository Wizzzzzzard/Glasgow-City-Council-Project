FME workspace Live and One Past Datetime Flow Pipeline.fmw

DateTime_Creator: Creator
    GEOMTYPE = Geometry Object
    NUM = 1
    CREATED -> AttributeCreator
AttributeCreator
    ATTR_TABLE = SET_TO Today = @DateTimeNow()
    -> DateTimeCalculator
DateTimeCalculator
    MODE = DATETIMECALC_1_ADD_INTERVAL
    OPERATION_PARAMETERS = START_DATETIME]@Value(Today)]OPERATOR]SUBTRACT]YEARS]0]MONTHS]0]DAYS]7]HOURS]0]MINUTES]0]SECONDS]0]RESULT_DATETIME]one_week_ago]FME_CONTROLLER_QUERY_FILE]transformers/dependencies/datetimecalculator/DATETIMECALC_1_ADD_INTERVAL.fme]FME_CONTROLLER_CHOICE]DATETIMECALC_1_ADD_INTERVAL
    -> DateTimeConverter
DateTimeConverter
    DATETIME_ATTR = one_week_ago
    OUT_FORMAT = %Y-%m-%dT%H:%M:%S
    PASSTHROUGH = NO
    REPAIR_INPUT = YES
    -> StringConcatenator
StringConcatenator
    ACTION = Create New Attribute
    PARM_LINE = fme_basicstring:148%20%10:https://trafficcalculatorsapi.azurewebsites.net/api/Query?code=NhKmPGbfvYE3ZU1nV9JAIaq3IB2FaEmR5OvTpOmL0iaRNefKQh8ZLg==&period=Raw&format=csv&start=@Value(one_week_ago)&size=1500
    VAL_ATTR = DateTimeHTTPRequest
Creator
    GEOMTYPE = Geometry Object
    NUM = 1
    CREATED -> GET_LiveTraffic
GET_LiveTraffic: HTTPCaller
    CONNECTION_TIMEOUT_LENGTH = 60
    ERROR_ATTR = _error
    FILE_PATH_ATTR = _response_file_path
    FOLLOW_REDIRECTS = FOLLOW_WITH_GET
    HTTP_METHOD = POST
    MAX_HTTP_VERSION = HTTP_2
    MAX_TRANSFERS_IN_PROGRESS = 25
    OUTPUT_FILENAME = E:\elija\OneDrive\OneDrive - University of Strathclyde\Dissertation\1. Extract Junction and Link Data\Junction Text Files\temptraffic.csv
    REDIRECT_AUTH = ORIGINAL_DOMAIN_ONLY
    SAVE_FILE = File
    SAVE_MULTI = No
    STATUS_CODE_ATTR = _http_status_code
    TARGET_URL = https://gcc-prod-traffcom.azurewebsites.net/api/TraffcomMovement?code=fgQNq/D09o30C/Qpp1LCQpwiYsWAtPEGRPd2r4HsxkBlOgvPHJIbJQ==&format=csv&size=1800
    TRANSFER_TIMEOUT_LENGTH = 90
    UPLOAD_CONTENT_TYPE = Text (text/plain)
    UPLOAD_TYPE = Specify Upload Body
    USE_COOKIES = No
    VERIFY_SSL_CERTIFICATES = Yes
Historic_Data_Creator: Creator
    GEOMTYPE = Geometry Object
    NUM = 1
    CREATED -> GET_Historic_Data
GET_Historic_Data: HTTPCaller
    CONNECTION_TIMEOUT_LENGTH = 60
    ERROR_ATTR = _error
    FILE_PATH_ATTR = _response_file_path
    FOLLOW_REDIRECTS = FOLLOW_WITH_GET
    HTTP_METHOD = POST
    MAX_HTTP_VERSION = HTTP_2
    MAX_TRANSFERS_IN_PROGRESS = 25
    OUTPUT_FILENAME = historic_test.csv
    REDIRECT_AUTH = ORIGINAL_DOMAIN_ONLY
    SAVE_FILE = File
    SAVE_MULTI = No
    STATUS_CODE_ATTR = _http_status_code
    TARGET_URL = https://trafficcalculatorsapi.azurewebsites.net/api/Query?code=NhKmPGbfvYE3ZU1nV9JAIaq3IB2FaEmR5OvTpOmL0iaRNefKQh8ZLg==&period=Raw&format=csv&start=2021-08-02T12:09:45&size=1800
    TRANSFER_TIMEOUT_LENGTH = 90
    UPLOAD_CONTENT_TYPE = Text (text/plain)
    UPLOAD_TYPE = Specify Upload Body
    USE_COOKIES = No
    VERIFY_SSL_CERTIFICATES = Yes
